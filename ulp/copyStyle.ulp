/*
 *   Title : copyStyle.ulp
 * Version : 0.5 alpha 1
 *    Date : 02-Set-2017
 *  Author : Rachael Peterson
 *
 * Purpose : Copies the style of an object
 *
 * License : Creative Commons Attribution-ShareAlike 4.0 International
 *         : CC BY-SA 4.0
 *         : https://creativecommons.org/licenses/by-sa/4.0/
 *
 *******************************************************************************
 *                           (c)Copyright 2017                                 *
 *******************************************************************************
 * THIS SOFTWARE IS PROVIDED BY THE AUTHOR ``AS IS'' AND ANY EXPRESS OR IMPLIED
 * WARRANTIES, INCLUDING, BUT NOT LIMITED TO, THE IMPLIED WARRANTIES OF
 * MERCHANTABILITY AND FITNESS FOR A PARTICULAR PURPOSE ARE DISCLAIMED. IN NO
 * EVENT SHALL THE AUTHOR BE LIABLE FOR ANY DIRECT, INDIRECT, INCIDENTAL,
 * SPECIAL, EXEMPLARY, OR CONSEQUENTIAL DAMAGES (INCLUDING, BUT NOT LIMITED TO,
 * PROCUREMENT OF SUBSTITUTE GOODS OR SERVICES; LOSS OF USE, DATA, OR PROFITS;
 * OR BUSINESS INTERRUPTION) HOWEVER CAUSED AND ON ANY THEORY OF LIABILITY,
 * WHETHER IN CONTRACT, STRICT LIABILITY, OR TORT (INCLUDING NEGLIGENCE OR
 * OTHERWISE) ARISING IN ANY WAY OUT OF THE USE OF THIS SOFTWARE, EVEN IF
 * ADVISED OF THE POSSIBILITY OF SUCH DAMAGE.
 *
 */

#usage "en: Copies the style of an object.\n"
       "run copyStyle --install - Installs the utility to the board context menus.\n"
       "run copyStyle --version - Shows the version number of the ULP being called.\n"
       "run copyStyle --locate-ulp - Shows the location of the ULP being called (Useful for debug).\n"
       "run copyStyle --hole - Copies the style of a hole.\n"
       "run copyStyle --via - Copies the style of a via.\n"
       "run copyStyle --wire - Copies the style of a wire.\n"

string VERSION = "0.5 alpha 1 (02-Sep-2017 23:31)";

enum {NONE, HOLE, VIA, WIRE};
int mode = NONE;

for (int i = 1 ; i < argc ; i++) {

   string argument = "";
   if (argc > 0) {
      argument = argv[i];
      if (argument == "--install") {
         exit("edit .brd; set context hole 'Copy Style...' 'run copyStyle --hole';"
              "           set context via  'Copy Style...' 'run copyStyle --via';"
              "           set context wire 'Copy Style...' 'run copyStyle --wire';");
      } else if (argument == "--version") {
         string tmp = "ULP Version: " + VERSION;
         dlgMessageBox(tmp);
         exit(0);
      } else if (argument == "--locate-ulp") {
         dlgMessageBox(argv[0]);
         exit(0);
      } else if (argument == "--hole") {
		   mode = HOLE;
      } else if (argument == "--via") {
		   mode = VIA;
      } else if (argument == "--wire") {
		   mode = WIRE;
      } else {
         // Do nothing at the moment
         dlgMessageBox("ERROR: Incorrect parameter(s) specified. See the usage instructions for further information.");
	   }
   }
}

if (board) {

   // Define variables

   string cmd = "GRID mil; ";

   int startLayer = 0;
   int endLayer = 0;
   string viaLayers = "";

   real drillValue = 0.0;
   real diameterValue = 0.0;
   real widthValue = 0.0;

   string shapeList[] = {"Square", "Round", "Octagon"};
   int shapeValue = 0;

   string tmp = "";

   board(B) {
      switch (mode) {
         case NONE:
            dlgMessageBox("ERROR: Missing parameter(s). See the usage instructions for further information.");
            break;
         case HOLE:
            B.holes(H) {
               if (ingroup(H)) {
                  drillValue = u2mil(H.drill);
               }
            }
            cmd += "CHA DRI ";
            sprintf(tmp, "%f; ", drillValue);
            cmd += tmp;
            cmd += "; GRID LAST; ";
            break;
         case VIA:
            B.signals(S) {
               S.vias(V) {
                  if (ingroup(V)) {
                     drillValue = u2mil(V.drill);
                     diameterValue = u2mil(V.diameter[1]);
                     shapeValue = V.shape[1];
                     startLayer = V.start;
                     endLayer = V.end;
                  }
               }
            }
            cmd += "CHA DRI ";
            sprintf(tmp, "%f; ", drillValue);
            cmd += tmp;
            cmd += "; CHA DIA ";
            sprintf(tmp, "%f; ", diameterValue);
            cmd += tmp;
            cmd += "; CHA SHA ";
            sprintf(tmp, "%s; ", shapeList[shapeValue]);
            cmd += tmp;
            cmd += "; GRID LAST; VIA ";
            sprintf(tmp, "%d-%d;", startLayer, endLayer);
            cmd += tmp;
            break;
         case WIRE:
            B.signals(S) {
               S.wires(W) {
                  if (ingroup(W)) {
                     widthValue = u2mil(W.width);
                  }
               }
            }
            cmd += "CHA WID ";
            sprintf(tmp, "%f; ", widthValue);
            cmd += tmp;
            cmd += "; GRID LAST;";
            break;
         default:
            dlgMessageBox("ERROR: An unspecified error has occurred. See the usage instructions for further information.");
            break;
      }
   }

   exit(cmd);

} else {
   dlgMessageBox("ERROR: This ULP is intended to be run in the board view.");
}
