/*
 *   Title : groupNet.ulp
 * Version : 0.1 alpha 1
 *    Date : 09-May-2017
 *  Author : Rachael Peterson
 *
 * Purpose : Facilitates easily adding all wire segments to a group
 *
 * License : Creative Commons Attribution-ShareAlike 4.0 International
 *         : CC BY-SA 4.0
 *         : https://creativecommons.org/licenses/by-sa/4.0/
 *
 *******************************************************************************
 *                           (c)Copyright 2017                                 *
 *******************************************************************************
 * THIS SOFTWARE IS PROVIDED BY THE AUTHOR ``AS IS'' AND ANY EXPRESS OR IMPLIED
 * WARRANTIES, INCLUDING, BUT NOT LIMITED TO, THE IMPLIED WARRANTIES OF
 * MERCHANTABILITY AND FITNESS FOR A PARTICULAR PURPOSE ARE DISCLAIMED. IN NO
 * EVENT SHALL THE AUTHOR BE LIABLE FOR ANY DIRECT, INDIRECT, INCIDENTAL,
 * SPECIAL, EXEMPLARY, OR CONSEQUENTIAL DAMAGES (INCLUDING, BUT NOT LIMITED TO,
 * PROCUREMENT OF SUBSTITUTE GOODS OR SERVICES; LOSS OF USE, DATA, OR PROFITS;
 * OR BUSINESS INTERRUPTION) HOWEVER CAUSED AND ON ANY THEORY OF LIABILITY,
 * WHETHER IN CONTRACT, STRICT LIABILITY, OR TORT (INCLUDING NEGLIGENCE OR
 * OTHERWISE) ARISING IN ANY WAY OUT OF THE USE OF THIS SOFTWARE, EVEN IF
 * ADVISED OF THE POSSIBILITY OF SUCH DAMAGE.
 *
 */

#usage "en: Enables an entire net to be added to a group.\n"
       "run groupNet --install - Installs the utility to the board context menus.\n"
       "run groupNet --version - Shows the version number of the ULP being called.\n"
       "run groupNet --locate-ulp - Shows the location of the ULP being called (Useful for debug).\n"

string VERSION = "0.1 alpha 1 (09-May-2017 18:58)";

if (argv[1] == "--install") {
   exit("edit .brd; set context wire 'Group Net...' 'run groupNet --interactive';");
} else if (argv[1] == "--version"){
   string tmp = "ULP Version: " + VERSION;
   dlgMessageBox(tmp);
   exit(0);
} else if (argv[1] == "--locate-ulp"){
   dlgMessageBox(argv[0]);
   exit(0);
} else {

   // Define variables

   string cmd="";

   if (board) {
      board(B) {
         B.signals(S) {
            if (ingroup(S)) {
               S.wires(W) {
                  setgroup(W);
               }
            }
         }
      }
   }

   exit(cmd);

}
