/*
 *   Title : changeVia.ulp
 * Version : 0.7 alpha 1
 *    Date : 02-Jun-2017
 *  Author : Rachael Peterson
 *
 * Purpose : Facilitates easily adding all wire segments to a group
 *
 * License : Creative Commons Attribution-ShareAlike 4.0 International
 *         : CC BY-SA 4.0
 *         : https://creativecommons.org/licenses/by-sa/4.0/
 *
 *******************************************************************************
 *                           (c)Copyright 2017                                 *
 *******************************************************************************
 * THIS SOFTWARE IS PROVIDED BY THE AUTHOR ``AS IS'' AND ANY EXPRESS OR IMPLIED
 * WARRANTIES, INCLUDING, BUT NOT LIMITED TO, THE IMPLIED WARRANTIES OF
 * MERCHANTABILITY AND FITNESS FOR A PARTICULAR PURPOSE ARE DISCLAIMED. IN NO
 * EVENT SHALL THE AUTHOR BE LIABLE FOR ANY DIRECT, INDIRECT, INCIDENTAL,
 * SPECIAL, EXEMPLARY, OR CONSEQUENTIAL DAMAGES (INCLUDING, BUT NOT LIMITED TO,
 * PROCUREMENT OF SUBSTITUTE GOODS OR SERVICES; LOSS OF USE, DATA, OR PROFITS;
 * OR BUSINESS INTERRUPTION) HOWEVER CAUSED AND ON ANY THEORY OF LIABILITY,
 * WHETHER IN CONTRACT, STRICT LIABILITY, OR TORT (INCLUDING NEGLIGENCE OR
 * OTHERWISE) ARISING IN ANY WAY OUT OF THE USE OF THIS SOFTWARE, EVEN IF
 * ADVISED OF THE POSSIBILITY OF SUCH DAMAGE.
 *
 */

#usage "en: Enables via types to be easily changed globally within a board.\n"
       "run changeVia --install - Installs the utility to the board context menus.\n"
       "run changeVia --version - Shows the version number of the ULP being called.\n"
       "run changeVia --locate-ulp - Shows the location of the ULP being called (Useful for debug).\n"

string VERSION = "0.7 alpha 1 (02-Jun-2017 14:07)";

if (argv[1] == "--install") {
   exit("edit .brd; set context via 'Change Via...' 'run changeVia --context';");
} else if (argv[1] == "--version"){
   string tmp = "ULP Version: " + VERSION;
   dlgMessageBox(tmp);
   exit(0);
} else if (argv[1] == "--locate-ulp"){
   dlgMessageBox(argv[0]);
   exit(0);
} else {

   // Define variables

   string cmd = "";
   int result = -1;

   string viaList[];
   int viaListLength = 0;
   int selected = 0;

   int startLayer = 0;
   int endLayer = 0;
   string viaLayers = "";

   real drillValue = 0.0;
   real diameterValue = 0.0;

   string shapeList[] = {"Square", "Round", "Octagon"};
   int shapeValue = 0;

   string pointsList = "";

   string tmp = "";

   if (board) {
      board(B) {
         B.signals(S) {
            S.vias(V) {
               string viaInfo = "";
               int viaFound = 0;
               if (V.diameter[LAYER_VIAS] == 0.0) {
                  sprintf(viaInfo, "%d-%d\t%s\t%.3f mil\tauto\t%.3f mil\t%.3f mil", V.start, V.end, shapeList[V.shape[V.start]], u2mil(V.drill), u2mil(V.diameter[1]), u2mil(V.diameter[2]));
               } else {
                  sprintf(viaInfo, "%d-%d\t%s\t%.3f mil\t%.3f mil\t%.3f mil\t%.3f mil", V.start, V.end, shapeList[V.shape[V.start]], u2mil(V.drill), u2mil(V.diameter[LAYER_VIAS]), u2mil(V.diameter[1]), u2mil(V.diameter[2]));
               }
               for (int i=0 ; i<=viaListLength ; i++) {
                  if (viaList[i] == viaInfo) {
                     viaFound = 1;
                  }
               }
               if (viaFound == 0) {
                  viaList[viaListLength++] = viaInfo;
               }
            }
            if (argv[1] == "--context") {
               S.vias(V) {
                  if (ingroup(V)) {
                     string viaInfo = "";
                     int viaFound = 0;
                     if (V.diameter[LAYER_VIAS] == 0.0) {
                        sprintf(viaInfo, "%d-%d\t%s\t%.3f mil\tauto\t%.3f mil\t%.3f mil", V.start, V.end, shapeList[V.shape[V.start]], u2mil(V.drill), u2mil(V.diameter[1]), u2mil(V.diameter[2]));
                     } else {
                        sprintf(viaInfo, "%d-%d\t%s\t%.3f mil\t%.3f mil\t%.3f mil\t%.3f mil", V.start, V.end, shapeList[V.shape[V.start]], u2mil(V.drill), u2mil(V.diameter[LAYER_VIAS]), u2mil(V.diameter[1]), u2mil(V.diameter[2]));
                     }
                     for (int i=0 ; i<=viaListLength ; i++) {
                        if (viaList[i] == viaInfo) {
                           selected = i;
                        }
                     }
                  }
               }
            }
         }
      }

      result = dlgDialog("List/Update Vias") { // Create the dialog
         // List all the vias in the design and extract the parameters of the selected
         dlgListView("Layers\tShape\tDrill\tDiameter\tOuter Diameter\tInner Diameter", viaList, selected) {
         if (dlgSelectionChanged()) {
            board(B) {
               B.signals(S) {
                  S.vias(V) {
                     string viaInfo = "";
                     if (V.diameter[LAYER_VIAS] == 0.0) {
                        sprintf(viaInfo, "%d-%d\t%s\t%.3f mil\tauto\t%.3f mil\t%.3f mil", V.start, V.end, shapeList[V.shape[V.start]], u2mil(V.drill), u2mil(V.diameter[1]), u2mil(V.diameter[2]));
                     } else {
                        sprintf(viaInfo, "%d-%d\t%s\t%.3f mil\t%.3f mil\t%.3f mil\t%.3f mil", V.start, V.end, shapeList[V.shape[V.start]], u2mil(V.drill), u2mil(V.diameter[LAYER_VIAS]), u2mil(V.diameter[1]), u2mil(V.diameter[2]));
                     }
                     if (viaList[selected] == viaInfo) {
                        startLayer = V.start;
                        endLayer = V.end;
                        sprintf(viaLayers, "%d-%d", startLayer, endLayer);
                        drillValue = u2mil(V.drill);
                        diameterValue = u2mil(V.diameter[LAYER_VIAS]);
                        shapeValue = V.shape[V.start];
                     }
                  }
               }
            }
            dlgRedisplay();
         }

         }
         // Enable updated parameters to be specified
         dlgHBoxLayout {
            dlgLabel("Layers*:");
            dlgStringEdit(viaLayers);
         }
         dlgHBoxLayout {
            dlgLabel("Drill Size:");
            dlgRealEdit(drillValue, 0.0, 9999.99);
            dlgLabel("mil");
         }
         dlgHBoxLayout {
            dlgLabel("Pad diameter:");
            dlgRealEdit(diameterValue, 0.0, 9999.99);
            dlgLabel("mil");
         }
         dlgHBoxLayout {
            dlgLabel("Pad shape:");
            dlgComboBox(shapeList, shapeValue) {}
         }
         dlgHBoxLayout {
            dlgLabel("* Read Only. Changing the value will have no effect.");
         }

         // Add the usual dialog buttons to proceed (OK) or abandon changes (Cancel)
         dlgHBoxLayout {
            dlgStretch(1);
            dlgPushButton("-Cancel") {
               //if (dlgMessageBox("Are you sure?", "Yes", "No") == 0) dlgReject(-1);
               dlgReject(-1);
            }
            dlgPushButton("+&OK") dlgAccept(0);
         }
      };

   }

   if (result == 0) {

      board(B) {
         B.signals(S) {
            S.vias(V) {
               if (argv[1] == "--context") {
                  if (ingroup(V)) {
                     sprintf(tmp, "(%f %f) ", u2mil(V.x), u2mil(V.y));
                     pointsList += tmp;
                  }
               } else {
                  string viaInfo = "";
                  if (V.diameter[LAYER_VIAS] == 0.0) {
                     sprintf(viaInfo, "%d-%d\t%s\t%.3f mil\tauto\t%.3f mil\t%.3f mil", V.start, V.end, shapeList[V.shape[V.start]], u2mil(V.drill), u2mil(V.diameter[1]), u2mil(V.diameter[2]));
                  } else {
                     sprintf(viaInfo, "%d-%d\t%s\t%.3f mil\t%.3f mil\t%.3f mil\t%.3f mil", V.start, V.end, shapeList[V.shape[V.start]], u2mil(V.drill), u2mil(V.diameter[LAYER_VIAS]), u2mil(V.diameter[1]), u2mil(V.diameter[2]));
                  }
                  if (viaList[selected] == viaInfo) {
                     sprintf(tmp, "(%f %f) ", u2mil(V.x), u2mil(V.y));
                     pointsList += tmp;
                  }
               }
            }
         }
      }

      cmd += "GRID mil; CHA DRI ";
      sprintf(tmp, "%f ", drillValue);
      cmd += tmp;
      cmd += pointsList;

      cmd += "; CHA DIA ";
      sprintf(tmp, "%f ", diameterValue);
      cmd += tmp;
      cmd += pointsList;

      cmd += "; CHA SHA ";
      sprintf(tmp, "%s ", shapeList[shapeValue]);
      cmd += tmp;
      cmd += pointsList;

      cmd += "; GRID LAST;";

   }

   exit(cmd);

}
