/*
 *   Title : unlock.ulp
 * Version : 0.1 alpha 1
 *    Date : 04-Jul-2017
 *  Author : Rachael Peterson
 *
 * Purpose : Provide the ability to unlock parts from the command line
 *
 * License : Creative Commons Attribution-ShareAlike 4.0 International
 *         : CC BY-SA 4.0
 *         : https://creativecommons.org/licenses/by-sa/4.0/
 *
 *******************************************************************************
 *                           (c)Copyright 2017                                 *
 *******************************************************************************
 * THIS SOFTWARE IS PROVIDED BY THE AUTHOR ``AS IS'' AND ANY EXPRESS OR IMPLIED
 * WARRANTIES, INCLUDING, BUT NOT LIMITED TO, THE IMPLIED WARRANTIES OF
 * MERCHANTABILITY AND FITNESS FOR A PARTICULAR PURPOSE ARE DISCLAIMED. IN NO
 * EVENT SHALL THE AUTHOR BE LIABLE FOR ANY DIRECT, INDIRECT, INCIDENTAL,
 * SPECIAL, EXEMPLARY, OR CONSEQUENTIAL DAMAGES (INCLUDING, BUT NOT LIMITED TO,
 * PROCUREMENT OF SUBSTITUTE GOODS OR SERVICES; LOSS OF USE, DATA, OR PROFITS;
 * OR BUSINESS INTERRUPTION) HOWEVER CAUSED AND ON ANY THEORY OF LIABILITY,
 * WHETHER IN CONTRACT, STRICT LIABILITY, OR TORT (INCLUDING NEGLIGENCE OR
 * OTHERWISE) ARISING IN ANY WAY OUT OF THE USE OF THIS SOFTWARE, EVEN IF
 * ADVISED OF THE POSSIBILITY OF SUCH DAMAGE.
 *
 */

#usage "en: Performs the opposite of LOCK <refdesList> when run from the command line.\n"
       "run unlock --version - Shows the version number of the ULP being called.\n"
       "run unlock --locate-ulp - Shows the location of the ULP being called (Useful for debug).\n"

string VERSION = "0.1 alpha 1 (07-Jul-2017 09:04)";

string tmp = "";

if (argv[1] == "--version"){
   string tmp = "ULP Version: " + VERSION;
   dlgMessageBox(tmp);
   exit(0);
} else if (argv[1] == "--locate-ulp"){
   dlgMessageBox(argv[0]);
   exit(0);
} else if (board) {

   string cmd="GRID mil; LOCK";
   int i = 1;

   while (argv[i] != "") {
      board(B) {
         B.elements(E) {
            if (E.name == strupr(argv[i])) {
               sprintf(tmp, " (S %f %f)", u2mil(E.x), u2mil(E.y));
               cmd+=tmp;
            }
         }
      }
      i++;
   }

   cmd += "; GRID LAST;";

   exit(cmd);

} else {
   dlgMessageBox(":ERROR: This utility is for use from within the board editor only.");
   exit(0);
}
