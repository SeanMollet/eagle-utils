/*
 *   Title : moveTools.ulp
 * Version : 0.1 alpha 1
 *    Date : 26-Oct-2017
 *  Author : Rachael Peterson
 *
 * Purpose : Adds context menu and dialogs for simplifying complex placement
 *           requirements.
 *
 * License : Creative Commons Attribution-ShareAlike 4.0 International
 *         : CC BY-SA 4.0
 *         : https://creativecommons.org/licenses/by-sa/4.0/
 *
 *******************************************************************************
 *                           (c)Copyright 2017                                 *
 *******************************************************************************
 * THIS SOFTWARE IS PROVIDED BY THE AUTHOR ``AS IS'' AND ANY EXPRESS OR IMPLIED
 * WARRANTIES, INCLUDING, BUT NOT LIMITED TO, THE IMPLIED WARRANTIES OF
 * MERCHANTABILITY AND FITNESS FOR A PARTICULAR PURPOSE ARE DISCLAIMED. IN NO
 * EVENT SHALL THE AUTHOR BE LIABLE FOR ANY DIRECT, INDIRECT, INCIDENTAL,
 * SPECIAL, EXEMPLARY, OR CONSEQUENTIAL DAMAGES (INCLUDING, BUT NOT LIMITED TO,
 * PROCUREMENT OF SUBSTITUTE GOODS OR SERVICES; LOSS OF USE, DATA, OR PROFITS;
 * OR BUSINESS INTERRUPTION) HOWEVER CAUSED AND ON ANY THEORY OF LIABILITY,
 * WHETHER IN CONTRACT, STRICT LIABILITY, OR TORT (INCLUDING NEGLIGENCE OR
 * OTHERWISE) ARISING IN ANY WAY OUT OF THE USE OF THIS SOFTWARE, EVEN IF
 * ADVISED OF THE POSSIBILITY OF SUCH DAMAGE.
 *
 */

#usage "en: Provices enhances move tools.\n"
       "run moveTools --install - Installs the utility to the board context menus.\n"
       "run moveTools --version - Shows the version number of the ULP being called.\n"
       "run moveTools --locate-ulp - Shows the location of the ULP being called (Useful for debug).\n"
       "run moveTools --set-mark - Sets a mark at the current components location.\n"
       "run moveTools --move - Moves to the absolute position specified.\n"
       "run moveTools --move-again - Performs the last used move operation again.\n"

// Global variables

int moveMode = 0;
string name = "";
int group = 0;
int setMark = 0;
string displayUnits[] = {"Microns", "Millimeters", "Mils", "Inches"};
string gridUnits[] = {"MIC", "MM", "MIL", "IN"};
int xunit = 2;
int yunit = 2;
string xinput = "0";
real xval = 0.0;
string yinput = "0";
real yval = 0.0;
int clearGroup = 0;
string groupName = "";

// Help Data

string helpTitle[];
string helpData[];
enum {ABT,SCH,BRD,CMD,LIC,DIS};

helpTitle[ABT] = "About moveTools";
helpData[ABT]  = "";

helpTitle[SCH] = "Schematic Usage";
helpData[SCH]  = "";

helpTitle[BRD] = "Board Usage";
helpData[BRD]  = "";

helpTitle[CMD] = "Command Line Usage";
helpData[CMD]  = "<p>The following lists the available usage options on the EAGLE command line:</p>"
                 "<code>run moveTools --install</code><br />"
                 "<code>run moveTools --version</code><br />"
                 "<code>run moveTools --about</code><br />"
                 "<code>run moveTools --help</code><br />"
                 "<code>run moveTools --license</code><br />"
                 "<code>run moveTools --set-mark</code><br />"
                 "<code>run moveTools --move[=<i>name</i>] [--group]</code><br />"
                 "<code>run moveTools --move-again[=<i>name</i>] [--group]</code>"
                 "<p>Where:</p>"
                 "<p><table>"
                 "<tr><td><code>--install&nbsp;</code></td><td>Install the shortcuts and context menu integrations.</td></tr>"
                 "<tr><td><code>--version&nbsp;</code></td><td>Displays the version, build date and time of the installed moveTools ULP.</td></tr>"
                 "<tr><td><code>--about&nbsp;</code></td><td>Shows the \'About moveTools\' tab of the help dialog.</td></tr>"
                 "<tr><td><code>--help&nbsp;</code></td><td>Displays the \'Command Line Usage\' tab of the help dialog.</td></tr>"
                 "<tr><td><code>--license&nbsp;</code></td><td>Displays the \'License\' tab of the help dialog, with the option to confirm acceptance of the terms.</td></tr>"
                 "<tr><td><code>--set-mark&nbsp;</code></td><td>Sets a MARK point in the editor at the location of the selected object.</td></tr>"
                 "<tr><td><code>--move&nbsp;</code></td><td>Performs a MOVE operation and allows specification of the parameters.</td></tr>"
                 "<tr><td><code>--move-again&nbsp;</code></td><td>Performs a MOVE oprtation using the previously specified parameters.</td></tr>"
                 "<tr><td><code>--group&nbsp;</code></td><td>Indicates that the <code>--move</code> or <code>--move-again</code> is to be performed on the currently specified group.</td></tr>"
                 "</table></p>";

helpTitle[LIC] = "Licence";
helpData[LIC]  = "<h2 align=\"center\">License : Creative Commons Attribution-ShareAlike 4.0 International</h2>"
                 "<h2 align=\"center\">(CC BY-SA 4.0)</h2>"
                 "<p align=\"center\"><a href=\"https://creativecommons.org/licenses/by-sa/4.0/\">https://creativecommons.org/licenses/by-sa/4.0/</a></p>"
                 "<hr />"
                 "<p align=\"center\">This is a human-readable summary of (and not a substitute for) the <a href=\"https://creativecommons.org/licenses/by-sa/4.0/\">license</a>.</p>"
                 "<h2 align=\"center\">You are free to:</h2>"
                 "<p align=\"justify\"><b>Share</b> — copy and redistribute the material in any medium or format.</p>"
                 "<p align=\"justify\"><b>Adapt</b> — remix, transform, and build upon the material for any purpose, even commercially.</p>"
                 "<p align=\"justify\">This license is acceptable for Free Cultural Works.</p>"
                 "<p align=\"justify\">The licensor cannot revoke these freedoms as long as you follow the license terms.</p>"
                 "<h2 align=\"center\">Under the following terms:</h2>"
                 "<p align=\"justify\"><b>Attribution</b> — You must give appropriate credit, provide a link to the license, and indicate if changes were made. You may do so in any reasonable manner, but not in any way that suggests the licensor endorses you or your use.</p>"
                 "<p align=\"justify\"><b>ShareAlike</b> — If you remix, transform, or build upon the material, you must distribute your contributions under the same license as the original.</p>"
                 "<p align=\"justify\"><b>No additional restrictions</b> — You may not apply legal terms or technological measures that legally restrict others from doing anything the license permits.</p>"
                 "<h2 align=\"center\">Notices:</h2>"
                 "<p align=\"justify\">You do not have to comply with the license for elements of the material in the public domain or where your use is permitted by an applicable exception or limitation.</p>"
                 "<p align=\"justify\">No warranties are given. The license may not give you all of the permissions necessary for your intended use. For example, other rights such as publicity, privacy, or moral rights may limit how you use the material.</p>";


helpTitle[DIS] = "Disclaimer";
helpData[DIS]  = "<p align=\"justify\">THIS SOFTWARE IS PROVIDED BY THE AUTHOR \"AS IS\" AND ANY EXPRESS OR IMPLIED "
                 "WARRANTIES, INCLUDING, BUT NOT LIMITED TO, THE IMPLIED WARRANTIES OF "
                 "MERCHANTABILITY AND FITNESS FOR A PARTICULAR PURPOSE ARE DISCLAIMED. IN NO "
                 "EVENT SHALL THE AUTHOR BE LIABLE FOR ANY DIRECT, INDIRECT, INCIDENTAL, "
                 "SPECIAL, EXEMPLARY, OR CONSEQUENTIAL DAMAGES (INCLUDING, BUT NOT LIMITED TO, "
                 "PROCUREMENT OF SUBSTITUTE GOODS OR SERVICES; LOSS OF USE, DATA, OR PROFITS; "
                 "OR BUSINESS INTERRUPTION) HOWEVER CAUSED AND ON ANY THEORY OF LIABILITY, "
                 "WHETHER IN CONTRACT, STRICT LIABILITY, OR TORT (INCLUDING NEGLIGENCE OR "
                 "OTHERWISE) ARISING IN ANY WAY OUT OF THE USE OF THIS SOFTWARE, EVEN IF "
                 "ADVISED OF THE POSSIBILITY OF SUCH DAMAGE.</P>";

// Helper functions

string ltostr (int value) {
   string strValue = "";
   sprintf (strValue, "%d", value);
   return strValue;
}

string dtostr (real value) {
   string strValue = "";
   sprintf (strValue, "%f", value);
   return strValue;
}

real utogrid(int u, int g) {
   switch (g) {
      case GRID_UNIT_MIC:
         return u2mic(u);
         break;

      case GRID_UNIT_MM: //
         return u2mm(u);
         break;

      case GRID_UNIT_MIL:
         return u2mil(u);
         break;

      case GRID_UNIT_INCH:
         return u2inch(u);
         break;

      default:
         dlgMessageBox("ERROR: Abnormal parameter passed to utogrid() function.");
         exit(0);
         break;
   }
}

/*
 *    Function : licenseCheck()
 * Description : Checks whether the terms of the license have been accepted
 */

int licenseCheck() {
   return strtol(cfgget("ULP:moveTools.licenseAccept", "0"));
}

/*
 *    Function : licenseCheck()
 * Description : Checks whether the terms of the license have been accepted
 */

void licenseConfirm(int licAccept) {
   cfgset("ULP:moveTools.licenseAccept", ltostr(licAccept));
}

/*
 *    Function : getMoveValues()
 * Description : Retrieve the previously specified values from the config
 */

int getMoveValues () {
   int sts = -1; // Dummy return value. Not currently used

   // Load the move parameters
   if (board) {
      moveMode = strtol(cfgget("ULP:moveTools.brd.moveMode", "1"));
      setMark = strtol(cfgget("ULP:moveTools.brd.setMark", "0"));
      xval = strtod(cfgget("ULP:moveTools.brd.xval", "0"));
      xinput = dtostr(xval);
      xunit = strtol(cfgget("ULP:moveTools.brd.xunit", "2"));
      yval = strtod(cfgget("ULP:moveTools.brd.yval", "0"));
      yinput = dtostr(yval);
      yunit = strtol(cfgget("ULP:moveTools.brd.yunit", "2"));
   } else if (schematic) {
      moveMode = strtol(cfgget("ULP:moveTools.sch.moveMode", "1"));
      setMark = strtol(cfgget("ULP:moveTools.sch.setMark", "0"));
      xval = strtod(cfgget("ULP:moveTools.sch.xval", "0"));
      xinput = dtostr(xval);
      xunit = strtol(cfgget("ULP:moveTools.sch.xunit", "3"));
      yval = strtod(cfgget("ULP:moveTools.sch.yval", "0"));
      yinput = dtostr(yval);
      yunit = strtol(cfgget("ULP:moveTools.sch.yunit", "3"));
   } else if (library) {
      moveMode = strtol(cfgget("ULP:moveTools.lbr.moveMode", "1"));
      setMark = strtol(cfgget("ULP:moveTools.lbr.setMark", "0"));
      xval = strtod(cfgget("ULP:moveTools.lbr.xval", "0"));
      xinput = dtostr(xval);
      xunit = strtol(cfgget("ULP:moveTools.lbr.xunit", "2"));
      yval = strtod(cfgget("ULP:moveTools.lbr.yval", "0"));
      yinput = dtostr(yval);
      yunit = strtol(cfgget("ULP:moveTools.lbr.yunit", "2"));
   } else {
      dlgMessageBox("ERROR: Unsupported editor detected");
      exit(-1);
   }

   return sts;
}

/*
 *    Function : setMoveValues()
 * Description : Store the currently specified values to the config
 */

int setMoveValues () {
   int sts = -1; // Dummy return value. Not currently used

   // Store the move parameters
   if (board) {
      cfgset("ULP:moveTools.brd.moveMode", ltostr(moveMode));
      cfgset("ULP:moveTools.brd.setMark", ltostr(setMark));
      cfgset("ULP:moveTools.brd.xval", dtostr(xval));
      cfgset("ULP:moveTools.brd.xunit", ltostr(xunit));
      cfgset("ULP:moveTools.brd.yval", dtostr(yval));
      cfgset("ULP:moveTools.brd.yunit", ltostr(yunit));
   } else if (schematic) {
      cfgset("ULP:moveTools.sch.moveMode", ltostr(moveMode));
      cfgset("ULP:moveTools.sch.setMark", ltostr(setMark));
      cfgset("ULP:moveTools.sch.xval", dtostr(xval));
      cfgset("ULP:moveTools.sch.xunit", ltostr(xunit));
      cfgset("ULP:moveTools.sch.yval", dtostr(yval));
      cfgset("ULP:moveTools.sch.yunit", ltostr(yunit));
   } else if (library) {
      cfgset("ULP:moveTools.lbr.moveMode", ltostr(moveMode));
      cfgset("ULP:moveTools.lbr.setMark", ltostr(setMark));
      cfgset("ULP:moveTools.lbr.xval", dtostr(xval));
      cfgset("ULP:moveTools.lbr.xunit", ltostr(xunit));
      cfgset("ULP:moveTools.lbr.yval", dtostr(yval));
      cfgset("ULP:moveTools.lbr.yunit", ltostr(yunit));
   } else {
      dlgMessageBox("ERROR: Unsupported editor detected");
   }

   return sts;
}

/*
 *    Function : helpUI()
 * Description : Create the help dialog
 */

int helpUI (int tabNum) {

   int result = dlgDialog ("Help") {
      dlgHBoxLayout {
         dlgSpacing(800);
      }
      dlgGroup("") {
         dlgTabWidget (tabNum) {
            for (int i=0 ; helpTitle[i] ; i++) {
               dlgTabPage (helpTitle[i]) {
                  dlgTextView(helpData[i]);
                  if (i == LIC || i == DIS) {
                     int licAccept = licenseCheck();
                     dlgHBoxLayout {
                        dlgStretch(1);
                        dlgCheckBox("I confirm I have read, understood, and accept the term of the licnese and disclaimer.", licAccept) {
                           licenseConfirm(licAccept);
                        }
                        dlgStretch(1);
                     }
                  }
               }
            }
         }
      }
      dlgHBoxLayout {
         dlgStretch(1);
         dlgPushButton("+OK") {
            dlgAccept(1);
         }
         dlgStretch(1);
      }
   };

   return result;
}

/*
 *    Function : brdMoveUI()
 * Description : Create the user interface for the board editor
 */

int brdMoveUI () {

   getMoveValues();

   int result = dlgDialog ("Set Move Parameters...") {
      dlgGroup("") {
         if (!group) {
            dlgGroup ("Move Mode") {
               dlgRadioButton("Absolute", moveMode) {
                  dlgRedisplay();
               }
               dlgRadioButton("Relative to self", moveMode) {
                  dlgRedisplay();
               }
               dlgRadioButton("Relative to mark", moveMode) {
                  dlgRedisplay();
               }
            }
         }
         dlgGroup("Set Position") {
            dlgHBoxLayout {
               dlgLabel("X:");
               dlgStringEdit(xinput);
               dlgComboBox(displayUnits, xunit);
               dlgLabel("Y:");
               dlgStringEdit(yinput);
               dlgComboBox(displayUnits, yunit);
            }
            dlgHBoxLayout {
               if (!group) {
                  dlgCheckBox("Update mark to new location", setMark);
               }
            }
         }
      }
      dlgHBoxLayout {
         dlgPushButton("Help...") {
            helpUI(BRD);
         }
         dlgStretch(1);
         dlgPushButton("Cancel") dlgReject(0);
         dlgPushButton("+OK") {
            xval = strtod(xinput);
            yval = strtod(yinput);
            setMoveValues();
            dlgAccept(1);
         }
      }
   };

   return result;
}

/*
 *    Function : schMoveUI()
 * Description : Create the user interface for the schematic editor
 */

int schMoveUI () {

   getMoveValues();

   real xinputd = trunc(strtod(xinput) * 10.0) / 10.0;
   sprintf(xinput, "%.1f", xinputd);
   real yinputd = trunc(strtod(yinput) * 10.0) / 10.0;
   sprintf(yinput, "%.1f", yinputd);

   int result = dlgDialog ("Set Move Parameters...") {
      dlgGroup("") {
         if (!group) {
            dlgGroup ("Move Mode") {
               dlgRadioButton("Absolute", moveMode) {
                  dlgRedisplay();
               }
               dlgRadioButton("Relative to self", moveMode) {
                  dlgRedisplay();
               }
               dlgRadioButton("Relative to mark", moveMode) {
                  dlgRedisplay();
               }
            }
         }
         dlgGroup("Set Position") {
            dlgHBoxLayout {
               dlgLabel("X:");
               dlgStringEdit(xinput);
               dlgLabel("Inch.");
               dlgLabel("Y:");
               dlgStringEdit(yinput);
               dlgLabel("Inch.");
               dlgStretch(1);
            }
            dlgHBoxLayout {
               if (!group) {
                  dlgCheckBox("Update mark to new location", setMark);
               }
            }
         }
         dlgLabel("NOTE: Schematic grid of 0.1\" enforced by this utility.");

      }
      dlgHBoxLayout {
         dlgPushButton("Help...") {
            helpUI(SCH);
         }
         dlgStretch(1);
         dlgPushButton("Cancel") dlgReject(0);
         dlgPushButton("+OK") {
            xinputd = strtod(xinput) * 10.0;
            xinput = dtostr(trunc(xinputd) / 10.0);
            xval = strtod(xinput);
            yinputd = strtod(yinput) * 10.0;
            yinput = dtostr(trunc(yinputd) / 10.0);
            yval = strtod(yinput);
            setMoveValues();
            dlgAccept(1);
         }
      }
   };

   return result;
}

// Main code

string VERSION = "0.5 alpha 1 (29-Oct-2017 17:36)";

enum {NONE, SETMARK, MOVE};
int mode = NONE;
int gui = 0;

if (!licenseCheck()) {
   helpUI(LIC);
}
if (licenseCheck()) {
   for (int i = 1 ; i < argc ; i++) {

      string argument[] = {""};
      if (argc > 0) {
         int numParams = strsplit(argument, argv[i], '=') - 1;
         if (argument[0] == "--install") {
            exit("edit .brd; set context element  'Set Mark...'   'run moveTools --set-mark';"
                 "           set context element  'Move To...'    'run moveTools --move';"
                 "           set context element  'Move Again...' 'run moveTools --move-again';"
                 "edit .sch; set context instance 'Set Mark...'   'run moveTools --set-mark';"
                 "           set context instance 'Move To...'    'run moveTools --move';"
                 "           set context instance 'Move Again...' 'run moveTools --move-again';");
         } else if (argument[0] == "--version") {
            string tmp = "ULP Version: " + VERSION;
            dlgMessageBox(tmp);
            exit(0);
         } else if (argument[0] == "--locate-ulp") {
            dlgMessageBox(argv[0]);
            exit(0);
         } else if (argument[0] == "--about") {
            helpUI(ABT);
            exit(0);
         } else if (argument[0] == "--help") {
            helpUI(CMD);
            exit(0);
         } else if (argument[0] == "--license") {
            helpUI(LIC);
            exit(0);
         } else if (argument[0] == "--set-mark") {
   		   mode = SETMARK;
         } else if (argument[0] == "--move") {
            if (numParams) {
               name = argument[1];
            }
   		   mode = MOVE;
            gui = 1;
         } else if (argument[0] == "--move-again") {
            if (numParams) {
               name = argument[1];
            }
   		   mode = MOVE;
            gui = 0;
         } else if (argument[0] == "--group") {
            group = 1;
         } else {
            // Do nothing at the moment
            dlgMessageBox("ERROR: Incorrect parameter(s) specified. See the usage instructions for further information.");
   	   }
      }
   }
} else {
   dlgMessageBox("ERROR: You must confirm you have read, understood and accept the terms of the license in order to use this utility.");
   exit(0);
}

if (board) {

   // Define variables

   string cmd = "GRID FINEST; ";
   string tmp = "";

   real currentX  = 0.0;
   real currentY  = 0.0;
   real currentGD = 0.0;
   int  currentGU = 0;

   board(B) {
      switch (mode) {

         case NONE:
            dlgMessageBox("ERROR: Missing parameter(s). See the usage instructions for further information.");
            break;

         case SETMARK:
            B.elements(E){
               if (ingroup(E)) {
                  sprintf(tmp, "MARK (%fMIL %fMIL)", u2mil(E.x), u2mil(E.y));
                  cmd += tmp;
               }
            }
            cmd += "; GRID LAST; ";
            break;

         case MOVE:
            B.elements(E) {
               if (ingroup(E)) {
                  if (!name) {
                     name = E.name;
                  }
               }
            }
            int result = 1; // Default to running the commands if no UI
            if (gui) {
               result = brdMoveUI();
            } else {
               getMoveValues();
            }
            if (result == 0) {
               cmd = "";
            } else {
               B.elements(E) {
                  if (ingroup(E)) {
                     if (E.name == name) {
                        currentX  = E.x;
                        currentY  = E.y;
                        currentGD = B.grid.distance;
                        currentGU = B.grid.unitdist;
                     }
                  }
               }
               if (!group) {
                  if (moveMode == 0) {
                     sprintf(tmp, "MOVE %s (%f%s %f%s)", name, xval, gridUnits[xunit], yval, gridUnits[yunit]);
                     cmd += tmp;
                     if (setMark) {
                        sprintf(tmp, "; MARK (%f%s %f%s)", xval, gridUnits[xunit], yval, gridUnits[yunit]);
                        cmd += tmp;
                     }
                  } else if (moveMode == 1) {
                     sprintf(tmp, "MOVE %s (%f%s %f%s)", name, utogrid(currentX,xunit)+xval, gridUnits[xunit], utogrid(currentY,yunit)+yval, gridUnits[yunit]);
                     cmd += tmp;
                     if (setMark) {
                        sprintf(tmp, "; MARK (%f%s %f%s)", utogrid(currentX,xunit)+xval, gridUnits[xunit], utogrid(currentY,yunit)+yval, gridUnits[yunit]);
                        cmd += tmp;
                     }
                  } else if (moveMode == 2) {
                     sprintf(tmp, "MOVE %s (R%f%s %f%s)", name, xval, gridUnits[xunit], yval, gridUnits[yunit]);
                     cmd += tmp;
                     if (setMark) {
                        sprintf(tmp, "; MARK (R%f%s %f%s)", xval, gridUnits[xunit], yval, gridUnits[yunit]);
                        cmd += tmp;
                     }
                  }
               } else {
                  sprintf(tmp, "MOVE (>0 0) (%f%s %f%s)", xval, gridUnits[xunit], yval, gridUnits[yunit]);
                  cmd += tmp;
               }
               cmd += "; GRID LAST; ";
            }
            break;

         default:
            dlgMessageBox("ERROR: An unspecified error has occurred. See the usage instructions for further information.");
            break;

      }
   }

   exit(cmd);

} else if (schematic) {

   // Define variables

   string cmd = "GRID IN 0.1; ";
   string tmp = "";

   real currentX  = 0.0;
   real currentY  = 0.0;

   sheet(SH) {
      switch (mode) {

         case NONE:
            dlgMessageBox("ERROR: Missing parameter(s). See the usage instructions for further information.");
            break;

         case SETMARK:
            SH.instances(I){
               if (ingroup(I)) {
                  sprintf(tmp, "MARK (%fMIL %fMIL)", u2mil(I.x), u2mil(I.y));
                  cmd += tmp;
               }
            }
            cmd += "; GRID LAST; ";
            break;

         case MOVE:
            SH.instances(I) {
               if (ingroup(I)) {
                  if (!name) {
                     name = I.name;
                  }
               }
            }
            int result = 1; // Default to running the commands if no UI
            if (gui) {
               result = schMoveUI();
            } else {
               getMoveValues();
            }
            if (result == 0) {
               cmd = "";
            } else {
               SH.instances(I) {
                  if (ingroup(I)) {
                     if (I.name == name) {
                        currentX  = I.x;
                        currentY  = I.y;
                     }
                  }
               }
               if (!group) {
                  if (moveMode == 0) {
                     sprintf(tmp, "MOVE %s (%f %f)", name, xval, yval);
                     cmd += tmp;
                     if (setMark) {
                        sprintf(tmp, "; MARK (%f %f)", xval, yval);
                        cmd += tmp;
                     }
                  } else if (moveMode == 1) {
                     sprintf(tmp, "MOVE %s (%f %f)", name, utogrid(currentX,GRID_UNIT_INCH)+xval, utogrid(currentY,GRID_UNIT_INCH)+yval);
                     cmd += tmp;
                     if (setMark) {
                        sprintf(tmp, "; MARK (%f %f)", utogrid(currentX,GRID_UNIT_INCH)+xval, utogrid(currentY,GRID_UNIT_INCH)+yval);
                        cmd += tmp;
                     }
                  } else if (moveMode == 2) {
                     sprintf(tmp, "MOVE %s (R%f %f)", name, xval, yval);
                     cmd += tmp;
                     if (setMark) {
                        sprintf(tmp, "; MARK (R%f %f)", xval, yval);
                        cmd += tmp;
                     }
                  }
               } else {
                  sprintf(tmp, "MOVE (>0 0) (%f %f)", xval, yval);
                  cmd += tmp;
               }
               cmd += "; GRID LAST; ";
            }

            break;

         default:
            dlgMessageBox("ERROR: An unspecified error has occurred. See the usage instructions for further information.");
            break;

      }
   }

   exit(cmd);

} else {
   dlgMessageBox("ERROR: This ULP is intended to be run in the board view.");
   exit(0);
}
